FME workspace AICOVERAGE_TO_BCGW.fmw
Title: AICOVERAGE_TO_BCGW
Description: List Source and Destination datasets and describe any inline data manipulations
Usage: Describe expected replication schedule
Requirements: List dependencies specific to this replication
Legal terms conditions: Any portion of this document, or any information supplied by the Province in relation to this document may not be used or disclosed for any purpose other than for DataBC Warehouse Population Services. Without limiting the generality of the foregoing, the User agrees to hold in confidence all information supplied by the Province in relation to this document.
Startup Python:
      import fme
      import DataBCFMWTemplate
      start = DataBCFMWTemplate.Start(fme)
      start.startup()
Shutdown Python:
      import fme
      import DataBCFMWTemplate
      shutIt = DataBCFMWTemplate.Shutdown(fme)
      shutIt.shutdown()

Parameters:
- SRC_DATASET_AICOV_1 = <SRC ARCINFO COVERAGE FOLDER>   # Source Arc/Info Coverage Folder
- SRC_FEATURE_1 = <SOURCE ARCINFO COVERAGE>   # Source Feature class
- DEST_SCHEMA = <DESTINATION SCHEMA>   # Destination Schema
- DEST_DB_ENV_KEY = DLV   # Destination Database Keyword (DLV|TST|PRD)
- DEST_FEATURE_1 = <DESTINATION TABLE>   # Destination Feature 1
- FILE_CHANGE_DETECTION = TRUE   # Whether to use file change detection or not
- LogURL = http://arneb.dmz/fmejobsubmitter/DWRSPUB/fme_logger.fmw   # Results Log URL
- NotificationEmail = dataetl@gov.bc.ca   # Notification Email
- DEST_INSTANCE:   # Python Script
      import DataBCFMWTemplate
      params = DataBCFMWTemplate.CalcParams(FME_MacroValues)
      return params.getDestinationInstance()
- LOGFILE:   # Python Script
      import DataBCFMWTemplate
      params = DataBCFMWTemplate.CalcParams(FME_MacroValues)
      return params.getFMWLogFileRelativePath()

Readers:
- ARCINFO_1: ARCINFO from $(SRC_DATASET_AICOV_1) in BCALB-83

Writers:
- SDE30_1: SDE30 to $(DEST_INSTANCE) in BCALB-83

Note: staging. / TPOD_BC_point
$(SRC_FEATURE_1) (reader ARCINFO_1)
    attributes: AREA float, PERIMETER float, TPOD_BC_ binint, TPOD_BC_ID binint, FCODE char(10), TPOD_TAG char(10), WRMAP_REF char(30), STRM_NAME char(30), STATUS char(2)
Note: Data Flow
File_Change_Detector_v2: File Change Detector v2
Note: whse_water_management. / BC_POINTS_OF_DIVERSION
$(DEST_SCHEMA).BC_POINTS_OF_DIVERSION (writer SDE30_1)
    attributes: FCODE char(10), TPOD_TAG char(10), OBJECTID integer, STRM_NAME char(30), STATUS char(2)

Bookmark: Setup and Configuration
Note: DELIVERY PACKAGE / Container structure / <container> / this workbench.fmw / <bin> / DataBCWhse.py / <docs> / fme2012template.docx / <outputs> / <audt> / etlFileChangeLog.txt / etlPopulationLog.txt / <failed_features> / {tester outputs} / <log> / this workbench.log
Note: FILE NAMING CONVENTION / Components, separated by underscore characters ( _ ) / Components: / Destination layer name (warehouse name in full) / _Source location / _Source format / _Destination location / .fmw / Examples: / cbm_intgd_cadastral_fabric_sp_icfprd_sde_idwdlvr1.fmw / raad_aoa_provincial_staging_shp_idwprod1.fmw / spi_wildlife_nonsensitive_sp_idwprod1_svw_idwprod1.fmw / site_env_remediation_sites_sp_idwprod1_odb_idwprod1.fmw
Note: WORKSPACE PROPERTIES / Complete workspace properties according to the instructions / provided as template values at the bottom of the Navigator widow

Bookmark: Readers and Writers
Note: SOURCE DATA / - Specify full UNC path name for file sources (no mappings) / - Delivery scripts should source delivery database instances / where they exist.
Note: DESTINATION DATA: DataBC Warehouse / Use one of the following writers for populating the warehouse: / - SDE30 (ESRI ArcSDE) / - ORACLE8I_DB (Oracle Non Spatial) / - ORACLE8I (Oracle Spatial Object) - by permission
Note: ORACLE NON SPATIAL AND SPATIAL OBJECT fast facts / - Destination Oracle Service: bcgwdlv.bcgov / - Username: <destination schema>
Note: ESRI ArcSDE (SDE30) WRITER fast facts / - Coordinate System: BCALB-83 / - ArcSDE Dataset: bcgwdlv.bcgov / - ArcSDE Server name: bcgwtst.bcgov / - Instance: port:5156 / - User ID: <destination schema>

Bookmark: Parameters and Settings
Note: DESTINATION FEATURE PARAMETERS / Available on the properties pagefor each Destination Feature: / - Table Exists: Yes / - Drop Table First: N / - Truncate Table First: Y
Note: WORKSPACE PARAMETERS / - Workspace Title: name of script, less file extension / - Log File: .\outputs\log\<Workspace Title>.log / - Password: <no password> / - Startup Python Script: <provided> / - Shutdown Python Script: <provided>
Note: PRIVATE PARAMETERS / Publish the following parameters: / - Any data source name / - Any destination data service name / Add new published parameters for any / destination dataset being populated, with / the following characteristics: / - Type: text / - Name: DestFeature* / - Prompt: Destination Feature * / - Default Value: <name of destination feature> / * a number to distinguish between / multiple destination features. / Template includes private parameters: / - LogURL: URL to centralized logging service / - NotificationEmail: contact email

Bookmark: File-based change detection
Note: Attach a file-based dataset reader to the / FILE SOURCE input. File-based data / sources will be analyzed to determine if they / have changed since they were last replicated.
Note: The CHANGES output routes features from a / file-based source deemed to have changed / since its last replication. / The NO_CHANGES output routes features / from a file based source deemed to not have / changed since its last replication.
Note: If you have multiple data sources, / you may duplicate the FileChangeDetector / for each one, or fan them into a single / FileChangeDetector and then fan them / out again afterwards, based on an / identifying attribute.

FME custom transformer ArcSDELockRemover
Test description

Parameters:
- Data_Source = bcgwdlv.bcgov   # Destination Instance
- User_ID =   # User ID
- Password =
